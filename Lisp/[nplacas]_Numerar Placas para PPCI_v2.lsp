(defun c:nplacas ()
(setq blip (getvar "blipmode" )
       eco (getvar "cmdecho" )
)
(setvar "blipmode" 0 )
(setvar "cmdecho" 0 )
(setq H (getdist "\nAltura da Letra:"))
(setq NI (getint "\nNumero inicial <1>: "))
(if (= NI nil)(setq NI 1))
(setq P1 (getpoint "\nPonto de insercao:"))   
(While (/= nil P1)
         (if (= P1 nil) (prompt "\n ")
             (progn
	            (setq aux (rtos NI 2 0))
	            (setq texto (strcat "placa n" aux))
                    (command "_.text" "s" "Standard" P1 H 0 texto)
                    (setq NI (+ NI 1))
              )
         ) 
(setq P1 (getpoint P1 "\nPonto de insercao:"))   
)
(setvar "cmdecho" eco )
(setvar "blipmode" blip )
(princ)
)
